FME workspace TweetStreamer.fmw

Parameters:
- DestDataset_CSV2 = C:\Users\swalker\Documents\GitHub\Web Data Module\fme-desktop-web-data\www   # Choose a folder to write the CSV of streamed tweets
- KEYWORD =   # Enter single keyword for tweet search (can be blank)

Writers:
- CSV2_1: CSV2 to $(DestDataset_CSV2) in LL84

Note: Start streaming
Note: Notes: / TweetStreamer is an unusual transformer in that it will continually run until the workspace is terminated. You can manually stop the translation, or you can alter the workspace to conduct tests (e.g. stream 500 tweets, run for a certain amount of time) and then terminate, or you can use FME Server to schedule streaming times. / Twitter's streaming API only allows you to filter by EITHER a search string or coordinates. You cannot simultaneously filter on both. Therefore, our transformer filters on a search string, and we filter out Tweets without geometry later. The keyword search has some peculiarities also, so check out the API docs for more details. / With more work, we could also keep Tweets with location information based on places or user profile data, but for now we'll just keep Tweets with coordinates. We could also set up the workspace to write to a database instead of CSV, changing TweetFilter.fmw to monitor the database for updates and add them to the GeoJSON when necessary.
Creator
    COORDSYS = EPSG:4326
    GEOM = <?xml version="1.0" encoding="US_ASCII" standalone="no" ?><geometry><polygon><line><coord x="-180" y="-90"/><coord x="180" y="-90"/><coord x="180" y="90"/><coord x="-180" y="90"/><coord x="-180" y="-90"/></line></polygon></geometry>
    GEOMTYPE = Geometry Object
    NUM = 1
    CREATED -> TweetStreamer
Note: Use Twitter streaming API to get real-time Tweets; see API docs for details on keywords
TweetStreamer
    KEYWORDS = $(KEYWORD)
    LANGUAGES = English
    TWITTER_CONNECTION = test Twitter
    USE_GEOMETRY = No
    TWEETS -> JSONFlattener
Note: Turn nested JSON structure into attribute table (with lists)
JSONFlattener
    ERROR_LIST_ATTR = _json_error
    JSON_DOCUMENT = @Value(_tweet_search_result)
    NEW_ATTRIBUTES = coordinates.coordinates{0} coordinates.coordinates{1} text source user.location
    READ_FROM_FILE = NO
    RECURSIVE = Yes
    -> Tester
Note: Filter tweets by hashtag and location data
Tester
    BOOL_OP = COMPOSITE
    COMPOSITE_TEST = 1 OR 2 AND 3
    TEST_CLAUSE:
      CASE_INSENSITIVE_TEST @Value(coordinates.coordinates{0}) != ""
      CASE_INSENSITIVE_TEST @Value(user.location) != ""
      CASE_INSENSITIVE_TEST @Value(text) CONTAINS $(KEYWORD)
    TEST_MODE = CASE_INSENSITIVE_TEST
    PASSED -> tweets (writer CSV2_1)
Note: Write to CSV
tweets (writer CSV2_1)
    attributes: _tweet_id string, _tweet_status string, _tweet_created_at string, _tweet_search_result string, _tweet_username string, coordinates.coordinates_0_ string, coordinates.coordinates_1_ string, text string, source string, user.location string
