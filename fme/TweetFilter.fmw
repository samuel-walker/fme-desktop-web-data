FME workspace TweetFilter.fmw

Parameters:
- DestDataset_GEOJSON = C:\Users\swalker\Documents\GitHub\Web Data Module\fme-desktop-web-data\www\tweets.json   # Destination GeoJSON File
- SourceDataset_CSV2 = C:\Users\swalker\Documents\GitHub\Web Data Module\fme-desktop-web-data\www\tweets.csv   # Source CSV (Comma Separated Value) File(s)
- TimeFilter = 20181120233723   # "{}" Display tweets after

Readers:
- CSV2_1: CSV2 from $(SourceDataset_CSV2)

Writers:
- GEOJSON_1: GEOJSON to $(DestDataset_GEOJSON) in EPSG:4326

Note: Read CSV (had to do dynamic to get long/lat, might not if starting from scratch)
CSV (reader CSV2_1)
    attributes: _tweet_id string, _tweet_status string, _tweet_created_at string, _tweet_search_result string, _tweet_username string, coordinates.coordinates_0_ string, coordinates.coordinates_1_ string, text string, source string, user.location string, _latitude string, _longitude string
    -> Tester
Tester
    BOOL_OP = OR
    COMPOSITE_TEST = 1
    TEST_CLAUSE = TEST @Value(_tweet_created_at) >= $(TimeFilter)
    TEST_MODE = TEST
    PASSED -> TestFilter
TestFilter
    DEFAULT_VALUE = No geometry
    TEST_LIST = "BOOL_OP,OR,COMPOSITE_TEST,""""""1"""""",TEST_CLAUSE,TEST @Value(coordinates.coordinates_0_) != """,Coordinates,"BOOL_OP,OR,COMPOSITE_TEST,""""""1"""""",TEST_CLAUSE,TEST @Value(user.location) != """,Geocoded
    Coordinates -> VertexCreator
    Geocoded -> Geocoder
Note: Turn string coordinates into point geometry
VertexCreator
    MEASURE_TYPE = Continuous
    MISSING_VAL_MODE = Compute
    MODE_NAME = Add Point
    XVAL = @Value(coordinates.coordinates_0_)
    YVAL = @Value(coordinates.coordinates_1_)
    -> Reprojector
Note: Geocode Twitter place name using HERE API. / NOTE: you will have to fill in your own API key here to use the Geocoder. If you don't want to do so, delete the Vertex_Creator_2 and the Geocoder.
Geocoder
    GEOCODING_SERVICE = HERE
    THREADS = 4
    TIMEOUT = 60
    -> VertexCreator_2
Note: Turn string coordinates from geocoder into point geometry
VertexCreator_2
    MEASURE_TYPE = Continuous
    MISSING_VAL_MODE = Compute
    MODE_NAME = Add Point
    XVAL = @Value(_longitude)
    YVAL = @Value(_latitude)
    -> Reprojector
Note: Project for Leaflet (might not be needed)
Reprojector
    DEST = EPSG:4326
    INTERPOLATION_TYPE_NAME = Nearest Neighbor
    RASTER_CELL_SIZE = Preserve Cells
    RASTER_TOLERANCE = 0.0
    SOURCE = Read from feature
    REPROJECTED -> JSONFlattener
Note: Extract attributes to form Tweet direct URL
JSONFlattener
    ERROR_LIST_ATTR = _json_error
    JSON_DOCUMENT = @Value(_tweet_search_result)
    NEW_ATTRIBUTES = user.screen_name id
    READ_FROM_FILE = NO
    RECURSIVE = Yes
    -> AttributeCreator
Note: Form URL from attributes
AttributeCreator
    ATTR_TABLE = SET_TO embed_url = https://twitter.com/@Value(user.screen_name)/status/@Value(id)
    -> HTTPCaller
Note: Use URL to query Twitter API, returns JSON with embed HTML
HTTPCaller
    CONNECTION_TIMEOUT_LENGTH = 60
    ERROR_ATTR = _error
    FOLLOW_REDIRECTS = Yes
    HTTP_METHOD = GET
    SAVE_FILE = Attribute
    STATUS_CODE_ATTR = _http_status_code
    TARGET_ATTR = _embed_json
    TARGET_ATTR_ENCODING = auto-detect
    TARGET_URL = https://publish.twitter.com/oembed?url=@Value(embed_url)
    TRANSFER_TIMEOUT_LENGTH = 90
    USE_COOKIES = No
    VERIFY_SSL_CERTIFICATES = Yes
    -> JSONExtractor
Note: Extract HTML from JSON
JSONExtractor
    EXTRACT_QUERY_TABLE = html json["html"]
    JSON_DOCUMENT = @Value(_embed_json)
    READ_FROM_FILE = NO
    EVALUATED -> tweets (writer GEOJSON_1)
Note: Write to GeoJSON
tweets (writer GEOJSON_1)
    attributes: embed_url string, _tweet_id string, _tweet_status string, _tweet_created_at string, _tweet_search_result string, _tweet_username string, coordinates.coordinates_0_ string, coordinates.coordinates_1_ string, text string, source string, user.location string, _latitude string, _longitude string, _address string, _address_json string, _address_types string, _arcgis_wkid string, _arcgis_longlabel string, _arcgis_exinfo string, _elevation_meters string, _elevation_feet string, _elevation_resolution string, _postal_code string, _tamu_census_block string, _tamu_census_tract string, _tamu_census_county_fips string, _tamu_census_cbsa_fips string, _tamu_census_mcd_fips string, _tamu_census_place_fips string, _tamu_census_state_fips string,
      _tamu_census_year string, _timezone string, _timezone_name string, _timezone_offset string, _timezone_current_dst string, user.screen_name string, id string, _embed_json string, _http_status_code string, html string
