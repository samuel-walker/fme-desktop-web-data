FME workspace TweetWorkspaceRunner.fmw

Creator
    GEOMTYPE = Geometry Object
    NUM = 1
    CREATED -> WorkspaceRunner
    CREATED -> Decelerator
WorkspaceRunner
    BLOCKING = No
    MAX_PROC = 1
    MAX_TO_BATCH = 1
    WORKSPACE_FILE = $(FME_MF_DIR)TweetStreamer.fmw
    WORKSPACE_PARAMETERS = DestDataset_CSV2,C:\Users\swalker\Documents\GitHub\Web Data Module\fme-desktop-web-data\www,KEYWORD,
Decelerator
    DECEL_TYPE = Per Feature Delay
    DELAY = 10
    -> WorkspaceScheduler [WorkspaceRunner_2_Input]
WorkspaceScheduler

FME custom transformer WorkspaceScheduler

WorkspaceRunner_2_Input (input)
    -> WorkspaceRunner_2
WorkspaceRunner_2
    BLOCKING = Yes
    WORKSPACE_FILE = $(FME_MF_DIR)TweetFilter.fmw
    WORKSPACE_PARAMETERS = DestDataset_GEOJSON,C:\Users\swalker\Documents\GitHub\Web Data Module\fme-desktop-web-data\www\tweets.json,SourceDataset_CSV2,C:\Users\swalker\Documents\GitHub\Web Data Module\fme-desktop-web-data\www\tweets.csv
    SUCCEEDED -> Decelerator
Decelerator
    DECEL_TYPE = Per Feature Delay
    DELAY = 60
    -> WorkspaceRunner_2_Input (output)
WorkspaceRunner_2_Input (output)
